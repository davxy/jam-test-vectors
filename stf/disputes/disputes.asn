-- Disputes STF test vectors schema

DisputesModule DEFINITIONS ::= BEGIN

IMPORTS
    TimeSlot, DisputesRecords, AvailabilityAssignments, ValidatorsData, DisputesExtrinsic,
    OffendersMark
        FROM JamTypes;


State ::= SEQUENCE {
    -- [ψ] Prior disputes verdicts and offenders. Mutated to ψ'.
    psi  DisputesRecords,
    -- [ρ] Prior availability cores assignments.
    rho AvailabilityAssignments,
    -- [τ] Prior timeslot.
    tau TimeSlot,
    -- [κ] Prior current epoch validators.
    kappa ValidatorsData,
    -- [λ] Prior previous epoch validators.
    lambda ValidatorsData
}

Input ::= SEQUENCE {
    -- [E_D] Disputes extrinsic
    disputes DisputesExtrinsic
}

OutputData ::= SEQUENCE {
    -- [H_o] Offenders marker
    offenders-mark OffendersMark
}

-- STF execution error codes.
-- Error codes **are not specified** in the the Graypaper.
-- Feel free to ignore the actual value.
ErrorCode ::= ENUMERATED {
    already-judged (0),
    bad-vote-split (1),
    verdicts-not-sorted-unique (2),
    judgements-not-sorted-unique (3),
    culprits-not-sorted-unique (4),
    faults-not-sorted-unique (5),
    not-enough-faults (6),
    culprits-verdict-not-bad (7),
    fault-verdict-wrong (8),
    offender-already-reported (9),
    bad-judgement-age (10),
    bad-validator-index (11),
    bad-signature (12),
    bad-guarantor-key (13),
    bad-auditor-key (14),
    bad-votes-count (15)
}

Output ::= CHOICE {
    ok    OutputData,
    err   ErrorCode
}

-- Disputes STF execution dump
TestCase ::= SEQUENCE {
    input        Input,
    pre-state    State,
    output       Output,
    post-state   State
}

END
