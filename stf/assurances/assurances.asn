-- Work reports assurances STF test vectors schema

ReportsModule DEFINITIONS ::= BEGIN

IMPORTS
    TimeSlot, ValidatorsData, HeaderHash, WorkReport,
    AvailabilityAssignments, AssurancesExtrinsic
        FROM JamTypes;


State ::= SEQUENCE {
    -- [ρ†] Intermediate pending reports after that any work report judged as
    -- uncertain or invalid has been removed from it. Mutated to ϱ‡.
    avail-assignments AvailabilityAssignments,

    -- [κ] Prior active validators.
    curr-validators ValidatorsData,
    -- [κ'] Posterior active validators.
    post-validators ValidatorsData
}

Input ::= SEQUENCE {
    -- [E_A] Assurances extrinsic.
    assurances AssurancesExtrinsic,

    -- [H_t] Block's timeslot.
    slot TimeSlot,

    -- [H_p] Parent hash.
    parent HeaderHash
}

-- State transition function execution error.
-- Error codes **are not specified** in the the Graypaper.
-- Feel free to ignore the actual value.
ErrorCode ::= ENUMERATED {
    bad-attestation-parent (0),
    bad-validator-index (1),
    core-not-engaged (2),
    bad-signature (3),
    not-sorted-or-unique-assurers (4)
}

OutputData ::= SEQUENCE {
    -- Items removed from ρ† to get ρ‡.
    reported SEQUENCE OF WorkReport
}

Output ::= CHOICE {
    ok  OutputData,
    err ErrorCode
}

TestCase ::= SEQUENCE {
    input        Input,
    pre-state    State,
    output       Output,
    post-state   State
}

END
